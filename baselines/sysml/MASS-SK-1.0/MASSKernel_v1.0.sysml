Skip to main panel





/
// ============================================================
// MASS SEMANTIC KERNEL — BASELINE METADATA
// ============================================================
//
// Baseline ID: MASS-SK-1.0
// Baseline Name: MASS Semantic Kernel v1.0
// SysML Package: MASSKernel
// Status: RELEASED
// Stage: 1.4
// Stage 1: COMPLETE
// Stage 1.4: COMPLETE
// Language: SysML v2
// Validation Environment: OMG SysML v2 Pilot Implementation
//
// Stage 1.3 Kernel Consistency Validation: COMPLETE
// SK1-SK16 Regression: PASS
// Cross-Semantic Contradiction Review: PASS
// Competency Questions CQ1-CQ12: 12/12 PASS
//
// Closed Kernel Gaps:
// K-GAP-01 Assessment Context Identity
// K-GAP-02 Collision-Risk Evidence Traceability
// K-GAP-03 Safety Applicability Context
// K-GAP-04 Remote Operation Context Identity
//
// NOTE:
// Runtime element UUIDs generated by the Pilot Implementation
// are not baseline identifiers.
//
// ============================================================

package MASSKernel {

    private import ScalarValues::*;

    // =====================================================
    // 1. STRUCTURAL FOUNDATION
    // =====================================================

    abstract part def System;

    abstract part def Vessel :> System;

    abstract part def Agent;

    abstract part def HumanAgent :> Agent;

    abstract part def TechnicalAgent :> Agent;


    part def RemoteOperationsCentre
        :> System;

    part def RemoteOperator
        :> HumanAgent;


    part def AutonomousNavigationSystem
        :> System, TechnicalAgent {

        ref item operationalDomains :
            OperationalDesignDomain[1..*];
    }


    // =====================================================
    // 2. MASS FUNCTIONS
    // =====================================================

    action def MASSFunction;

    action def NavigationFunction
        :> MASSFunction;

    action def CollisionAvoidanceFunction
        :> MASSFunction;

    // =====================================================
    // SK10 — ACTIVE FUNCTION REQUIRES PERFORMER
    // =====================================================

    constraint def SK10_ActiveFunctionRequiresPerformer {

    in functionActive :
        Boolean[1];

    in assignedPerformers :
        Agent[0..*];

    functionActive
        implies
    SequenceFunctions::size(assignedPerformers) >= 1
}
    // =====================================================
    // SK11 — ACTIVE FUNCTION REQUIRES EXACTLY ONE AUTHORITY HOLDER
    // =====================================================

    constraint def SK11_ActiveFunctionRequiresExactlyOneAuthorityHolder {

    in functionActive :
        Boolean[1];

    in authorityHolders :
        Agent[0..*];

    functionActive
        implies
    SequenceFunctions::size(authorityHolders) == 1
}  
    // =====================================================
    // SK12 — REMOTE OPERATION REQUIRES ACTIVE ROC
    // =====================================================

    constraint def SK12_RemoteOperationRequiresActiveROC {

    in remoteOperationActive :
        Boolean[1];

    in activeROCs :
        RemoteOperationsCentre[0..*];

    remoteOperationActive
        implies
    SequenceFunctions::size(activeROCs) >= 1
}
    // =====================================================
    // 3. OPERATIONAL DESIGN DOMAIN / ENVELOPE
    // =====================================================

    item def OperationalDesignDomain {

        assert constraint {
            true
        }
    }


    item def OperationalEnvelope {

        ref item includedODDs :
            OperationalDesignDomain[1..*];

        assert constraint {
            true
        }
    }


    // =====================================================
    // 4. MODE OF OPERATION
    // =====================================================

    state def ModeOfOperation;


    state def RemoteOperation
        :> ModeOfOperation;

    state def SupervisedAutonomy
        :> ModeOfOperation;

    state def AutonomousOperation
        :> ModeOfOperation;


    state def MASSOperationalMode {

        state remote :
            RemoteOperation;

        state supervised :
            SupervisedAutonomy;

        state autonomous :
            AutonomousOperation;
    }

    constraint def SK9_ExactlyOneActiveMode {

    in candidateActiveModes :
        ModeOfOperation[0..*];

    SequenceFunctions::size(candidateActiveModes) == 1
}


    // =====================================================
    // 5. OPERATIONAL CONDITION
    //    Orthogonal to ModeOfOperation
    // =====================================================

    state def OperationalCondition;


    state def NormalCondition
        :> OperationalCondition;

    state def DegradedState
        :> OperationalCondition;

    state def FallbackState
        :> OperationalCondition;

    constraint def SK8_AtLeastOneFallbackState {

    in fallbackStates :
        FallbackState[0..*];

    SequenceFunctions::size(fallbackStates) >= 1
}
    
    state def MASSOperationalCondition {

    state normal :
        NormalCondition;

    state degraded :
        DegradedState;

    state fallback :
        FallbackState;

    assert constraint sk8_AtLeastOneFallbackState :
        SK8_AtLeastOneFallbackState {

        in fallbackStates =
            fallback;
    }
}


    // =====================================================
    // OPERATIONAL CONDITION ASSESSMENT — SK6 / SK7
    // =====================================================

    constraint def SK6_SK7_OperationalConditionConsistency {

    in assessedFunctionWithinODD :
        Boolean[1];

    in assessedMASSWithinOE :
        Boolean[1];

    in assessedCondition :
        OperationalCondition[1];

    (
        (
            assessedMASSWithinOE
            and assessedFunctionWithinODD
        )
        implies
        (
            assessedCondition istype NormalCondition
        )
    )

    and

    (
        (
            assessedMASSWithinOE
            and not assessedFunctionWithinODD
        )
        implies
        (
            assessedCondition istype DegradedState
        )
    )

    and

    (
        (
            not assessedMASSWithinOE
        )
        implies
        (
            assessedCondition istype FallbackState
        )
    )
}


    // =====================================================
    // 6. MODE / FUNCTION / AGENT ASSIGNMENT
    // =====================================================

    item def ModeFunctionAssignment {

    ref state mode :
        ModeOfOperation[1];

    ref action function :
        MASSFunction[1];

    ref part performer :
        Agent[1..*];

    ref part supervisor :
        Agent[0..*];

    ref part authorityHolder :
        Agent[1];

    ref item effectiveODD :
        OperationalDesignDomain[1];


    assert constraint sk3_ExactlyOneEffectiveODD :
        SK3_ExactlyOneEffectiveODD {

        in effectiveODDs =
            effectiveODD;
    }
}

    item def AutonomousModeFunctionAssignment
    :> ModeFunctionAssignment {

    ref part autonomousPerformer :
        AutonomousNavigationSystem[1]
        subsets performer;

    assert constraint sk3b_EffectiveODDConsistentWithPerformer :
        SK3b_EffectiveODDConsistentWithPerformer {

        in performerODDs =
            autonomousPerformer.operationalDomains;

        in effectiveODDs =
            effectiveODD;
    }
}
    // =====================================================
    // 7. MASS
    // =====================================================
    constraint def SK3_ExactlyOneEffectiveODD {

    in effectiveODDs :
        OperationalDesignDomain[0..*];

    SequenceFunctions::size(effectiveODDs) == 1
}  
    constraint def SK3b_EffectiveODDConsistentWithPerformer {

    in performerODDs :
        OperationalDesignDomain[0..*];

    in effectiveODDs :
        OperationalDesignDomain[0..*];

    SequenceFunctions::includes(
        performerODDs,
        effectiveODDs
    )
} 
    constraint def SK5_ODDWithinOperationalEnvelope {

    in envelopeODDs :
        OperationalDesignDomain[1..*];

    in ansODDs :
        OperationalDesignDomain[0..*];

    SequenceFunctions::includes(
        envelopeODDs,
        ansODDs
    )
}
    constraint def SK4_ExactlyOneOperationalEnvelope {

    in envelopes :
        OperationalEnvelope[0..*];

    SequenceFunctions::size(envelopes) == 1
}
        part def MaritimeAutonomousSurfaceShip
        :> Vessel {

        part autonomousNavigationSystems :
            AutonomousNavigationSystem[0..*];

        perform action operationalFunctions :
            MASSFunction[1..*];

        ref item operationalEnvelope :
            OperationalEnvelope[1];

        ref item modeFunctionAssignments :
            ModeFunctionAssignment[0..*];

        exhibit state mode :
            MASSOperationalMode;

        exhibit state condition :
            MASSOperationalCondition;


        assert constraint sk4_ExactlyOneOperationalEnvelope :
            SK4_ExactlyOneOperationalEnvelope {

            in envelopes =
                operationalEnvelope;
        }


        // =====================================================
        // SK5
        // Every ODD used by onboard ANS shall belong
        // to the MASS Operational Envelope.
        // =====================================================

        assert constraint sk5_ODDWithinOperationalEnvelope :
            SK5_ODDWithinOperationalEnvelope {

            in envelopeODDs =
                operationalEnvelope.includedODDs;

            in ansODDs =
                autonomousNavigationSystems.operationalDomains;
        }

    } 


    // =====================================================
    // K-GAP-01 — ASSESSMENT CONTEXT IDENTITY
    // =====================================================

    constraint def OperationalAssessmentContextIdentity {

        in massAssignments :
            ModeFunctionAssignment[0..*];

        in assessedAssignments :
            ModeFunctionAssignment[0..*];

        SequenceFunctions::size(assessedAssignments) == 1
        and
        SequenceFunctions::includes(
            massAssignments,
            assessedAssignments
        )
    }


    // =====================================================
    // OPERATIONAL ASSESSMENT CONTEXT
    // =====================================================

    occurrence def OperationalAssessmentContext {

        ref part subjectMASS :
            MaritimeAutonomousSurfaceShip[1];

        ref item assignment :
            ModeFunctionAssignment[1];
    }


    // =====================================================
    // OPERATIONAL CONDITION ASSESSMENT
    // =====================================================

    item def OperationalConditionAssessment {

        ref occurrence context :
            OperationalAssessmentContext[1];

        attribute functionWithinODD :
            ScalarValues::Boolean[1];

        attribute massWithinOE :
            ScalarValues::Boolean[1];

        ref state requiredCondition :
            OperationalCondition[1];


        assert constraint sk6sk7_OperationalConditionConsistency :
            SK6_SK7_OperationalConditionConsistency {

            in assessedFunctionWithinODD =
                functionWithinODD;

            in assessedMASSWithinOE =
                massWithinOE;

            in assessedCondition =
                requiredCondition;
        }
    }


    // =====================================================
    // OPERATIONAL MODE SNAPSHOT
    // =====================================================

    occurrence def OperationalModeSnapshot {

        ref part subjectMASS :
            MaritimeAutonomousSurfaceShip[1];

        ref state activeModes :
            ModeOfOperation[0..*];

        assert constraint sk9_ExactlyOneActiveMode :
            SK9_ExactlyOneActiveMode {

            in candidateActiveModes =
                activeModes;
        }
    }
    

    // =====================================================
    // OPERATIONAL FUNCTION SNAPSHOT — SK10
    // =====================================================

    occurrence def OperationalFunctionSnapshot {

    ref part subjectMASS :
        MaritimeAutonomousSurfaceShip[1];

    ref action function :
        MASSFunction[1];

    attribute isActive :
        Boolean[1];

    ref part performers :
        Agent[0..*];

    ref part authorityHolders :
        Agent[0..*];
}

    // =====================================================
    // REMOTE OPERATION SNAPSHOT — SK12
    // =====================================================

    occurrence def RemoteOperationSnapshot {

    ref part subjectMASS :
        MaritimeAutonomousSurfaceShip[1];

    attribute remoteOperationActive :
        Boolean[1];

    ref part activeROCs :
        RemoteOperationsCentre[0..*];
}
     // 2. ADD

constraint def RemoteOperationContextIdentity {

    in sessionMASS :
        MaritimeAutonomousSurfaceShip[1];

    in sessionROC :
        RemoteOperationsCentre[1];

    in snapshotMASS :
        MaritimeAutonomousSurfaceShip[1];

    in snapshotActiveROCs :
        RemoteOperationsCentre[0..*];

    SequenceFunctions::includes(
        snapshotMASS,
        sessionMASS
    )
    and
    SequenceFunctions::includes(
        snapshotActiveROCs,
        sessionROC
    )
}


// 3. ADD

occurrence def RemoteOperationContext {

    ref occurrence session :
        RemoteOperationSession[1];

    ref occurrence remoteSnapshot :
        RemoteOperationSnapshot[1];
}
    // =====================================================
    // 8. ANALYSIS / OPERATIONAL SYSTEM BOUNDARY
    // =====================================================

    part def MASSOperationalSystem {

        ref part mass :
            MaritimeAutonomousSurfaceShip[1];

        ref part rocs :
            RemoteOperationsCentre[0..*];
    }


    // =====================================================
    // 9. MASS <-> ROC ASSOCIATION
    // =====================================================

    connection def ROCAssociation {

        end [1] part mass :
            MaritimeAutonomousSurfaceShip;

        end [1] part roc :
            RemoteOperationsCentre;
    }


    // =====================================================
    // 10. REMOTE OPERATION SESSION
    // =====================================================

    occurrence def RemoteOperationSession {

        ref part operator :
            RemoteOperator[1];

        ref part roc :
            RemoteOperationsCentre[1];

        ref part mass :
            MaritimeAutonomousSurfaceShip[1];

        ref action functions :
            MASSFunction[1..*];

        // 1. ADD to RemoteOperationSession

        connection rocAssociation :
            ROCAssociation
            connect mass references mass
            to roc references roc;
}
        

        constraint def SK13_AtLeastTwoParticipants {

        in vessels :
        Vessel[0..*];

        SequenceFunctions::size(vessels) >= 2
}
        // =====================================================
        // SK14 — EXACTLY ONE SUBJECT MASS
        // =====================================================

        constraint def SK14_ExactlyOneSubjectMASS {

       in subjectMASSes :
       MaritimeAutonomousSurfaceShip[0..*];

       SequenceFunctions::size(subjectMASSes) == 1
}

    // =====================================================
    // 11. COLREG SITUATIONS
    // =====================================================

    occurrence def COLREGSituation {

    ref part participants :
        Vessel[2..*];

    ref part subjectMASS :
        MaritimeAutonomousSurfaceShip[1]
        subsets participants;

    assert constraint sk13_AtLeastTwoParticipants :
        SK13_AtLeastTwoParticipants {

        in vessels =
            participants;
    }
}


    occurrence def CrossingSituation
        :> COLREGSituation;

    occurrence def HeadOnSituation
        :> COLREGSituation;

    occurrence def OvertakingSituation
        :> COLREGSituation;


    // =====================================================
    // 12. COLLISION RISK
    // =====================================================

    enum def CollisionRiskLevel {
        Low;
        Medium;
        High;
        Critical;
    }

    item def AssessmentEvidence;


        action def CollisionRiskAssessment {

        in ref occurrence situation :
            COLREGSituation[1];

        in item assessmentEvidence :
            AssessmentEvidence[1..*];

        out attribute riskLevel :
            CollisionRiskLevel[1];
    }
    // =====================================================
    // SK15 — COLLISION RISK RESULT HAS EXACTLY ONE
    //        ASSESSMENT CONTEXT
    // =====================================================

    constraint def SK15_ExactlyOneAssessmentContext {

    in assessmentContexts :
        CollisionRiskAssessment[0..*];

    SequenceFunctions::size(assessmentContexts) == 1
}


   // =====================================================
   // COLLISION RISK RESULT
   // =====================================================

   item def CollisionRiskResult {

    ref action assessmentContext :
        CollisionRiskAssessment[1];
}

    // =====================================================
    // 13. CONTROL
    // =====================================================

    action def ControlAction {

        in ref part issuedBy :
            Agent[1];

        in ref part actsOn :
            System[1..*];
    }

    // =====================================================
    // SK16 — SAFETY CONSTRAINT HAS EXACTLY ONE SUBJECT
    // =====================================================

    constraint def SK16_ExactlyOneSubject {

    in subjectCandidates[0..*];

    SequenceFunctions::size(subjectCandidates) == 1
}
    
    // =====================================================
    // SAFETY APPLICABILITY CONTEXT
    // =====================================================

    occurrence def SafetyApplicabilityContext {

        ref occurrence situation :
            COLREGSituation[0..1];

        ref action function :
            MASSFunction[0..1];

        ref action controlAction :
            ControlAction[0..1];
    }
    

    // =====================================================
    // 14. SAFETY REQUIREMENTS
    // =====================================================

        requirement def SafetyConstraint {

        subject constrainedElement;

        ref occurrence applicableContexts :
            SafetyApplicabilityContext[0..*];
    }

}
